FME workspace csv_to_sql_migrator.fmw

Parameters:
- SourceDataset_PATH_6 = N:\GI_SECTION\HPMS\Submissions   # INCLUDE_WEB_BROWSER Source Folder and File Pathnames Folder
- DeleteChoice = NO   # Do you wish to delete historic HPMS data
- ChooseYearDeletion = ALL   # What year(s) would you like to delete historic data from or choose "All" to delete every year.
- YearSelection = 2025_submission   # Select the submission year you would like to add to the SQL database
- DataItemChoice = cracking_percent,f_system,facility_type,faulting,iri,nhs,ownership,rutting,strahnet_type,urban_id   # Choose the data item(s) you would like to add or delete

Readers:
- PATH_4: PATH from $(SourceDataset_PATH_6)

PATH (reader PATH_4)
    attributes: path_unix buffer, path_windows buffer, path_rootname buffer, path_filename buffer, path_extension buffer, path_directory_unix buffer, path_directory_windows buffer, path_type char(10)
    -> TestFilter_16
TestFilter_16
    DEFAULT_VALUE = <UNFILTERED>
    PASSED_TEST_GROUP_OUTPUT = FIRST
    TEST_LIST = "BOOL_OP,OR,COMPOSITE_TEST,""""""1"""""",TEST_CLAUSE,TEST $(DeleteChoice) = YES",__DeleteChoice_ = Yes
    __DeleteChoice_ = Yes -> FeatureReader_7 [INITIATOR]
    <UNFILTERED> -> TestFilter
TestFilter
    DEFAULT_VALUE = <UNFILTERED>
    PASSED_TEST_GROUP_OUTPUT = ALL
    TEST_LIST = "BOOL_OP,OR,COMPOSITE_TEST,""""""1"""""",TEST_CLAUSE,CASE_INSENSITIVE_TEST @Value(path_rootname) IN $(YearSelection)",@Value(path_rootname) IN __YearSelection_
    @Value(path_rootname) IN __YearSelection_ -> FeatureReader_7 [INITIATOR]
FeatureReader_7
    ATTR_ACCUM_MODE = Only Use Result
    COMBINE_GEOM = Use Result
    DATASET = @Value(path_windows)
    FORMAT = PATH
    ORDER_RESULTS = No
    OUTPUT_FEATURES_DISPLAY = Schema and Data Features
    PATH_GLOB_PATTERN = *.csv
    PATH_HIDDEN_FILES = INCLUDE
    PATH_NO_EMPTY_PROPERTIES = YES
    PATH_OFFSET_DATETIME = yes
    PATH_RECURSE_DIRECTORIES = YES
    PATH_RETRIEVE_FILE_PROPERTIES = NO
    PATH_TYPE = FILE
    PATH_USE_NON_STRING_ATTR = yes
    INITIATOR -> FeatureReader_8 [INITIATOR]
FeatureReader_8
    ATTR_ACCUM_MODE = Only Use Result
    COMBINE_GEOM = Use Result
    DATASET = @Value(path_windows)
    FORMAT = PATH
    ORDER_RESULTS = No
    OUTPUT_FEATURES_DISPLAY = Schema and Data Features
    PATH_GLOB_PATTERN = *.csv
    PATH_HIDDEN_FILES = INCLUDE
    PATH_NO_EMPTY_PROPERTIES = YES
    PATH_OFFSET_DATETIME = yes
    PATH_RECURSE_DIRECTORIES = YES
    PATH_RETRIEVE_FILE_PROPERTIES = NO
    PATH_TYPE = FILE
    PATH_USE_NON_STRING_ATTR = yes
    <OTHER> -> AttributeExposer_4
AttributeExposer_4
    ATTR_TABLE = path_windows,
    -> DuplicateFilter_4
DuplicateFilter_4
    INPUT_ORDERED_CHOICE = No
    KEYATTR = path_windows
    UNIQUE -> TestFilter_4
TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST @Value(path_windows) CONTAINS summary",@Value(path_windows) CONTAINS summary,"BOOL_OP,OR,COMPOSITE_TEST,""""""1"""""",TEST_CLAUSE,CASE_INSENSITIVE_TEST @Value(path_windows) CONTAINS metadata",@Value(path_windows) CONTAINS metadata,"BOOL_OP,OR,COMPOSITE_TEST,""""""1"""""",TEST_CLAUSE,CASE_INSENSITIVE_TEST @Value(path_windows) CONTAINS Summaries",@Value(path_windows) CONTAINS Summaries,"BOOL_OP,OR,COMPOSITE_TEST,""""""1"""""",TEST_CLAUSE,CASE_INSENSITIVE_TEST @Value(path_windows) CONTAINS travel",@Value(path_windows) CONTAINS travel,"BOOL_OP,OR,COMPOSITE_TEST,""""""1"""""",TEST_CLAUSE,CASE_INSENSITIVE_TEST @Value(path_windows) CONTAINS by",@Value(path_windows) CONTAINS by,"BOOL_OP,OR,COMPOSITE_TEST,""""""1"""""",TEST_CLAUSE,CASE_INSENSITIVE_TEST @Value(path_windows) CONTAINS sample",@Value(path_windows) CONTAINS sample,"BOOL_OP,OR,COMPOSITE_TEST,""""""1"""""",TEST_CLAUSE,CASE_INSENSITIVE_TEST @Value(path_windows) CONTAINS validation",@Value(path_windows) CONTAINS validation,"BOOL_OP,OR,COMPOSITE_TEST,""""""1"""""",TEST_CLAUSE,CASE_INSENSITIVE_TEST @Value(path_windows) CONTAINS combined",@Value(path_windows) CONTAINS combined,"BOOL_OP,OR,COMPOSITE_TEST,""""""1"""""",TEST_CLAUSE,CASE_INSENSITIVE_TEST @Value(path_windows) CONTAINS ttm",@Value(path_windows) CONTAINS ttm,"BOOL_OP,OR,COMPOSITE_TEST,""""""1"""""",TEST_CLAUSE,CASE_INSENSITIVE_TEST @Value(path_windows) CONTAINS vanessa",@Value(path_windows) CONTAINS vanessa,"BOOL_OP,OR,COMPOSITE_TEST,""""""1"""""",TEST_CLAUSE,CASE_INSENSITIVE_TEST @Value(path_windows) CONTAINS all",@Value(path_windows) CONTAINS all,"BOOL_OP,OR,COMPOSITE_TEST,""""""1"""""",TEST_CLAUSE,CASE_INSENSITIVE_TEST @Value(path_windows) CONTAINS Arnold",@Value(path_windows) CONTAINS Arnold,"BOOL_OP,OR,COMPOSITE_TEST,""""""1"""""",TEST_CLAUSE,CASE_INSENSITIVE_TEST @Value(path_windows) CONTAINS olkds",@Value(path_windows) CONTAINS olkds,"BOOL_OP,OR,COMPOSITE_TEST,""""""1"""""",TEST_CLAUSE,CASE_INSENSITIVE_TEST @Value(path_windows) CONTAINS backup",@Value(path_windows) CONTAINS backup
    <UNFILTERED> -> TestFilter_5
TestFilter_5
    DEFAULT_VALUE = <UNFILTERED>
    PASSED_TEST_GROUP_OUTPUT = FIRST
    TEST_LIST = "BOOL_OP,OR,COMPOSITE_TEST,""""""1"""""",TEST_CLAUSE,CASE_INSENSITIVE_TEST @Value(path_windows) CONTAINS summary",@Value(path_windows) CONTAINS summary,"BOOL_OP,OR,COMPOSITE_TEST,""""""1"""""",TEST_CLAUSE,CASE_INSENSITIVE_TEST @Value(path_windows) CONTAINS metadata",@Value(path_windows) CONTAINS metadata,"BOOL_OP,OR,COMPOSITE_TEST,""""""1"""""",TEST_CLAUSE,CASE_INSENSITIVE_TEST @Value(path_windows) CONTAINS Summaries",@Value(path_windows) CONTAINS Summaries,"BOOL_OP,OR,COMPOSITE_TEST,""""""1"""""",TEST_CLAUSE,CASE_INSENSITIVE_TEST @Value(path_windows) CONTAINS travel",@Value(path_windows) CONTAINS travel,"BOOL_OP,OR,COMPOSITE_TEST,""""""1"""""",TEST_CLAUSE,CASE_INSENSITIVE_TEST @Value(path_windows) CONTAINS by",@Value(path_windows) CONTAINS by,"BOOL_OP,OR,COMPOSITE_TEST,""""""1"""""",TEST_CLAUSE,CASE_INSENSITIVE_TEST @Value(path_windows) CONTAINS sample",@Value(path_windows) CONTAINS sample,"BOOL_OP,OR,COMPOSITE_TEST,""""""1"""""",TEST_CLAUSE,CASE_INSENSITIVE_TEST @Value(path_windows) CONTAINS validation",@Value(path_windows) CONTAINS validation,"BOOL_OP,OR,COMPOSITE_TEST,""""""1"""""",TEST_CLAUSE,CASE_INSENSITIVE_TEST @Value(path_windows) CONTAINS combined",@Value(path_windows) CONTAINS combined,"BOOL_OP,OR,COMPOSITE_TEST,""""""1"""""",TEST_CLAUSE,CASE_INSENSITIVE_TEST @Value(path_windows) CONTAINS ttm",@Value(path_windows) CONTAINS ttm
    <UNFILTERED> -> TestFilter_6
TestFilter_6
    DEFAULT_VALUE = <UNFILTERED>
    PASSED_TEST_GROUP_OUTPUT = FIRST
    TEST_LIST = "BOOL_OP,OR,COMPOSITE_TEST,""""""1"""""",TEST_CLAUSE,CASE_INSENSITIVE_TEST @Value(path_windows) CONTAINS summary",@Value(path_windows) CONTAINS summary,"BOOL_OP,OR,COMPOSITE_TEST,""""""1"""""",TEST_CLAUSE,CASE_INSENSITIVE_TEST @Value(path_windows) CONTAINS metadata",@Value(path_windows) CONTAINS metadata,"BOOL_OP,OR,COMPOSITE_TEST,""""""1"""""",TEST_CLAUSE,CASE_INSENSITIVE_TEST @Value(path_windows) CONTAINS Summaries",@Value(path_windows) CONTAINS Summaries,"BOOL_OP,OR,COMPOSITE_TEST,""""""1"""""",TEST_CLAUSE,CASE_INSENSITIVE_TEST @Value(path_windows) CONTAINS travel",@Value(path_windows) CONTAINS travel,"BOOL_OP,OR,COMPOSITE_TEST,""""""1"""""",TEST_CLAUSE,CASE_INSENSITIVE_TEST @Value(path_windows) CONTAINS by",@Value(path_windows) CONTAINS by,"BOOL_OP,OR,COMPOSITE_TEST,""""""1"""""",TEST_CLAUSE,CASE_INSENSITIVE_TEST @Value(path_windows) CONTAINS sample",@Value(path_windows) CONTAINS sample,"BOOL_OP,OR,COMPOSITE_TEST,""""""1"""""",TEST_CLAUSE,CASE_INSENSITIVE_TEST @Value(path_windows) CONTAINS validation",@Value(path_windows) CONTAINS validation,"BOOL_OP,OR,COMPOSITE_TEST,""""""1"""""",TEST_CLAUSE,CASE_INSENSITIVE_TEST @Value(path_windows) CONTAINS combined",@Value(path_windows) CONTAINS combined,"BOOL_OP,OR,COMPOSITE_TEST,""""""1"""""",TEST_CLAUSE,CASE_INSENSITIVE_TEST @Value(path_windows) CONTAINS ttm",@Value(path_windows) CONTAINS ttm
    <UNFILTERED> -> FeatureReader [INITIATOR]
FeatureReader
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = |
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INTERACT = NONE
    ORDER_RESULTS = No
    OUTPUT_FEATURES_DISPLAY = Schema and Data Features
    <OTHER> -> AttributeExposer
AttributeExposer
    ATTR_TABLE = BeginPoint,,EndPoint,,Begin_Point,,End_Point,,ROUTEID,,Route_ID,,RouteID,,ValueNumeric,,Value_Numeric,,Value_Date,,ValueText,,Value_Text,,Section_Length,,SectionLength,,State_Code,,StateID,,Data_Item,,DataItem,,Comments,,BeginDate,,Year_Record,,BMP,,EMP,,Begin_Date,
    -> AttributeRemover
AttributeRemover
    REMOVE_ATTRS = attribute{0}.fme_data_type,attribute{0}.name,attribute{0}.native_data_type,fme_feature_type_name,fme_format_long_name,fme_format_short_name,fme_schema_handling,path_windows
    -> Logger_4
Logger_4
    LOG_FEATURE = NONE
    MAXFEATS = 20
    MESSAGE = I am being read
    SEVERITY = INFO
    LOGGED -> BulkAttributeRenamer
BulkAttributeRenamer
    ATTRCHOICE = Selected Attributes
    ATTRLIST = RouteID RouteId
    CASE_CHANGE_TYPE = upper
    MODE_CHOICE = RENAME
    PATTERN_ACTION_DISP = CASECHANGE
    -> TestFilter_14
TestFilter_14
    DEFAULT_VALUE = <UNFILTERED>
    PASSED_TEST_GROUP_OUTPUT = FIRST
    TEST_LIST:
      "BOOL_OP,OR,COMPOSITE_TEST,""""""1 OR 2 OR 3"""""",TEST_CLAUSE,CASE_INSENSITIVE_TEST @Value(Data_Item) IN $(DataItemChoice)
      CASE_INSENSITIVE_TEST @Value(DataItem) IN $(DataItemChoice)
      CASE_INSENSITIVE_TEST $(DataItemChoice) = """,@Value(Data_Item) IN __DataItemChoice_
    @Value(Data_Item) IN __DataItemChoice_ -> Logger
Logger
    LOG_FEATURE = NONE
    MAXFEATS = 20
    MESSAGE = Feature is: working correctly
    SEVERITY = INFO
    LOGGED -> AttributeRenamer
AttributeRenamer
    ATTR_TABLE:
      RENAME_SET_DEFAULT BeginPoint > BMP
      RENAME_SET_DEFAULT EndPoint > EMP
      RENAME_SET_DEFAULT Year_Record > BeginDate
      RENAME_SET_DEFAULT State_Code > StateID
      RENAME_SET_DEFAULT Route_ID > ROUTEID
      RENAME_SET_DEFAULT Begin_Point > BMP
      RENAME_SET_DEFAULT End_Point > EMP
      RENAME_SET_DEFAULT Data_Item > DataItem
      RENAME_SET_DEFAULT Value_Numeric > ValueNumeric
      RENAME_SET_DEFAULT Value_Text > ValueText
      RENAME_SET_DEFAULT Value_Date > ValueDate
      RENAME_SET_DEFAULT RouteId > ROUTEID
      RENAME_SET_DEFAULT StateId > StateID
      RENAME_SET_DEFAULT Begin_Date > BeginDate
    MISSING_INPUT_ATTRS = PRESERVE
    -> Logger_2
Logger_2
    LOG_FEATURE = NONE
    MAXFEATS = 20
    MESSAGE = Feature is: Attribute renamer working correctly
    SEVERITY = INFO
    LOGGED -> TestFilter_3
TestFilter_3
    DEFAULT_VALUE = <UNFILTERED>
    PASSED_TEST_GROUP_OUTPUT = FIRST
    TEST_LIST = "BOOL_OP,OR,COMPOSITE_TEST,""""""1"""""",TEST_CLAUSE,TEST @StringLength(@Value(BeginDate)) < 6",@StringLength(@Value(BeginDate)) < 6
    @StringLength(@Value(BeginDate)) < 6 -> StringConcatenator
    <UNFILTERED> -> AttributeCreator
StringConcatenator
    ACTION = Create New Attribute
    PARM_LINE = fme_basicstring:6%17:01/01/@Value(BeginDate)
    VAL_ATTR = BeginDate
    -> AttributeCreator
AttributeCreator
    ATTR_TABLE = SET_TO DataYear (varchar(200)) = @Substring(@Value(BeginDate),6,4)
    -> TestFilter_8
TestFilter_8
    DEFAULT_VALUE = <UNFILTERED>
    PASSED_TEST_GROUP_OUTPUT = FIRST
    TEST_LIST = "BOOL_OP,OR,COMPOSITE_TEST,""""""1"""""",TEST_CLAUSE,TEST @StringLength(@Value(DataYear)) < 4",@StringLength(@Value(DataYear)) < 4
    @StringLength(@Value(DataYear)) < 4 -> StringConcatenator_2
    <UNFILTERED> -> AttributeKeeper
StringConcatenator_2
    ACTION = Create New Attribute
    PARM_LINE = fme_basicstring:2%16:20@Value(DataYear)
    VAL_ATTR = DataYear
    -> AttributeKeeper
AttributeKeeper
    CREATE_BULK_MODE_FEATURES = NO
    KEEP_ATTRS = BeginDate,BMP,Comments,DataItem,DataYear,EMP,ROUTEID,StateID,ValueDate,ValueNumeric,ValueText
    -> StringCaseChanger
StringCaseChanger
    ATTRCHOICE = Selected Attributes
    ATTRLIST = DataItem
    CHANGE_TYPE = lowercase
    -> TestFilter_7
TestFilter_7
    DEFAULT_VALUE = <UNFILTERED>
    PASSED_TEST_GROUP_OUTPUT = FIRST
    TEST_LIST = "BOOL_OP,OR,COMPOSITE_TEST,""""""1"""""",TEST_CLAUSE,CASE_INSENSITIVE_TEST @Value(DataItem) CONTAINS county_code",@Value(DataItem) CONTAINS county_code
    @Value(DataItem) CONTAINS county_code -> StringReplacer_3
    <UNFILTERED> -> TestFilter_10
StringReplacer_3
    CASE = NO
    FIND_TEXT = county_code
    NO_MATCH = _FME_NO_OP_
    REGEXP = NO
    REPLACE_TEXT = county_id
    SRC_ATTRS = DataItem
    -> TestFilter_10
TestFilter_10
    DEFAULT_VALUE = <UNFILTERED>
    PASSED_TEST_GROUP_OUTPUT = FIRST
    TEST_LIST = "BOOL_OP,OR,COMPOSITE_TEST,""""""1"""""",TEST_CLAUSE,TEST $(DeleteChoice) = YES",__DeleteChoice_ = YES,"BOOL_OP,OR,COMPOSITE_TEST,""""""1"""""",TEST_CLAUSE,TEST $(DeleteChoice) = NO",__DeleteChoice_ = NO
    __DeleteChoice_ = YES -> TestFilter_15
    __DeleteChoice_ = NO -> TestFilter_2
TestFilter_2
    DEFAULT_VALUE = <UNFILTERED>
    PASSED_TEST_GROUP_OUTPUT = FIRST
    TEST_LIST = "BOOL_OP,OR,COMPOSITE_TEST,""""""1"""""",TEST_CLAUSE,CASE_INSENSITIVE_TEST @Value(DataItem) CONTAINS curves",@Value(DataItem) CONTAINS curves,"BOOL_OP,OR,COMPOSITE_TEST,""""""1"""""",TEST_CLAUSE,CASE_INSENSITIVE_TEST @Value(DataItem) CONTAINS grades",@Value(DataItem) CONTAINS grades
    @Value(DataItem) CONTAINS curves -> FeatureWriter_2 [Output]
    @Value(DataItem) CONTAINS grades -> FeatureWriter_2 [Output]
    <UNFILTERED> -> TestFilter_9
FeatureWriter_2
    DATASET = HPMS
    DATASET_ATTR = _dataset
    FEATURE_TYPE_LIST_ATTR = _feature_types
    FORMAT = MSSQL_ADO
    MSSQL_ADO_BULK_INSERT = YES
    MSSQL_ADO_COMMAND_TIMEOUT = 30
    MSSQL_ADO_COORDINATE_SYSTEM_GRANULARITY = FEATURE
    MSSQL_ADO_NAMED_CONNECTION = HPMS
    MSSQL_ADO_START_TRANSACTION = 0
    MSSQL_ADO_TRANSACTION_INTERVAL = 500
    TOTAL_FEATURES_WRITTEN_ATTR = _total_features_written
TestFilter_9
    DEFAULT_VALUE = <UNFILTERED>
    PASSED_TEST_GROUP_OUTPUT = FIRST
    TEST_LIST = "BOOL_OP,OR,COMPOSITE_TEST,""""""1"""""",TEST_CLAUSE,TEST ROUTEID ATTRIBUTE_VALUE_NULL """,ROUTEID ATTRIBUTE_VALUE_NULL,"BOOL_OP,OR,COMPOSITE_TEST,""""""1"""""",TEST_CLAUSE,TEST ROUTEID ATTRIBUTE_IS_MISSING """,ROUTEID ATTRIBUTE_IS_MISSING
    <UNFILTERED> -> TestFilter_13
TestFilter_13
    DEFAULT_VALUE = <UNFILTERED>
    PASSED_TEST_GROUP_OUTPUT = FIRST
    TEST_LIST = "BOOL_OP,OR,COMPOSITE_TEST,""""""1"""""",TEST_CLAUSE,CASE_INSENSITIVE_TEST @Value(DataItem) CONTAINS alternative",@Value(DataItem) CONTAINS alternative,"BOOL_OP,OR,COMPOSITE_TEST,""""""1"""""",TEST_CLAUSE,CASE_INSENSITIVE_TEST @Value(DataItem) CONTAINS flexible",@Value(DataItem) CONTAINS flexible,"BOOL_OP,OR,COMPOSITE_TEST,""""""1"""""",TEST_CLAUSE,CASE_INSENSITIVE_TEST @Value(DataItem) CONTAINS urban",@Value(DataItem) CONTAINS urban,"BOOL_OP,OR,COMPOSITE_TEST,""""""1"""""",TEST_CLAUSE,CASE_INSENSITIVE_TEST @Value(DataItem) CONTAINS pct_peak_single",@Value(DataItem) CONTAINS pct_peak_single,"BOOL_OP,OR,COMPOSITE_TEST,""""""1"""""",TEST_CLAUSE,CASE_INSENSITIVE_TEST @Value(DataItem) CONTAINS pct_peak_combination",@Value(DataItem) CONTAINS pct_peak_combination,"BOOL_OP,OR,COMPOSITE_TEST,""""""1"""""",TEST_CLAUSE,CASE_INSENSITIVE_TEST @Value(DataItem) CONTAINS truck",truck CONTAINS truck,"BOOL_OP,OR,COMPOSITE_TEST,""""""1"""""",TEST_CLAUSE,CASE_INSENSITIVE_TEST @Value(DataItem) CONTAINS pct_dh_single_unit",@Value(DataItem) CONTAINS pct_dh_single_unit,"BOOL_OP,OR,COMPOSITE_TEST,""""""1"""""",TEST_CLAUSE,TEST DataItem ATTRIBUTE_IS_MISSING """,DataItem ATTRIBUTE_IS_MISSING,"BOOL_OP,OR,COMPOSITE_TEST,""""""1"""""",TEST_CLAUSE,TEST DataItem ATTRIBUTE_IS_EMPTY """,DataItem ATTRIBUTE_IS_EMPTY,"BOOL_OP,OR,COMPOSITE_TEST,""""""1"""""",TEST_CLAUSE,TEST DataItem ATTRIBUTE_VALUE_NULL """,DataItem ATTRIBUTE_VALUE_NULL
    @Value(DataItem) CONTAINS alternative -> StringReplacer_11
    @Value(DataItem) CONTAINS flexible -> StringReplacer_12
    @Value(DataItem) CONTAINS urban -> StringReplacer_13
    @Value(DataItem) CONTAINS pct_peak_single -> StringReplacer_14
    @Value(DataItem) CONTAINS pct_peak_combination -> StringReplacer_15
    truck CONTAINS truck -> StringReplacer_16
    @Value(DataItem) CONTAINS pct_dh_single_unit -> StringReplacer_17
    <UNFILTERED> -> FeatureWriter [Output]
StringReplacer_11
    CASE = NO
    FIND_TEXT = alternative_route_name
    NO_MATCH = _FME_NO_OP_
    REGEXP = NO
    REPLACE_TEXT = route_name
    SRC_ATTRS = DataItem
    -> FeatureWriter [Output]
StringReplacer_12
    CASE = NO
    FIND_TEXT = thickness_flexible
    NO_MATCH = _FME_NO_OP_
    REGEXP = NO
    REPLACE_TEXT = thickness_flex
    SRC_ATTRS = DataItem
    -> FeatureWriter [Output]
StringReplacer_13
    CASE = NO
    FIND_TEXT = urban_code
    NO_MATCH = _FME_NO_OP_
    REGEXP = NO
    REPLACE_TEXT = urban_id
    SRC_ATTRS = DataItem
    -> FeatureWriter [Output]
StringReplacer_14
    CASE = NO
    FIND_TEXT = pct_peak_single
    NO_MATCH = _FME_NO_OP_
    REGEXP = NO
    REPLACE_TEXT = pct_dh_single
    SRC_ATTRS = DataItem
    -> FeatureWriter [Output]
StringReplacer_15
    CASE = NO
    FIND_TEXT = pct_peak_combination
    NO_MATCH = _FME_NO_OP_
    REGEXP = NO
    REPLACE_TEXT = pct_dh_combination
    SRC_ATTRS = DataItem
    -> FeatureWriter [Output]
StringReplacer_16
    CASE = NO
    FIND_TEXT = truck
    NO_MATCH = _FME_NO_OP_
    REGEXP = NO
    REPLACE_TEXT = nn
    SRC_ATTRS = DataItem
    -> FeatureWriter [Output]
StringReplacer_17
    CASE = NO
    FIND_TEXT = pct_dh_single_unit
    NO_MATCH = _FME_NO_OP_
    REGEXP = NO
    REPLACE_TEXT = pct_dh_single
    SRC_ATTRS = DataItem
    -> FeatureWriter [Output]
FeatureWriter
    DATASET = HPMS
    DATASET_ATTR = _dataset
    FEATURE_TYPE_LIST_ATTR = _feature_types
    FORMAT = MSSQL_ADO
    MSSQL_ADO_BULK_INSERT = NO
    MSSQL_ADO_COMMAND_TIMEOUT = 60
    MSSQL_ADO_COORDINATE_SYSTEM_GRANULARITY = FEATURE
    MSSQL_ADO_NAMED_CONNECTION = HPMS
    MSSQL_ADO_START_TRANSACTION = 0
    MSSQL_ADO_TRANSACTION_INTERVAL = 500
    TOTAL_FEATURES_WRITTEN_ATTR = _total_features_written
TestFilter_15
    DEFAULT_VALUE = <UNFILTERED>
    PASSED_TEST_GROUP_OUTPUT = FIRST
    TEST_LIST:
      "BOOL_OP,OR,COMPOSITE_TEST,""""""1 OR 2"""""",TEST_CLAUSE,TEST @Value(DataYear) IN $(ChooseYearDeletion)
      TEST $(ChooseYearDeletion) = ALL",@Value(DataYear) IN __ChooseYearDeletion_
    @Value(DataYear) IN __ChooseYearDeletion_ -> TestFilter_11
TestFilter_11
    DEFAULT_VALUE = <UNFILTERED>
    PASSED_TEST_GROUP_OUTPUT = FIRST
    TEST_LIST = "BOOL_OP,OR,COMPOSITE_TEST,""""""1"""""",TEST_CLAUSE,CASE_INSENSITIVE_TEST @Value(DataItem) CONTAINS curve",@Value(DataItem) CONTAINS curve,"BOOL_OP,OR,COMPOSITE_TEST,""""""1"""""",TEST_CLAUSE,CASE_INSENSITIVE_TEST @Value(DataItem) IN grades_a,grades_b,grades_c,grades_d,grades_e,grades_f",@Value(DataItem) IN grades_a,grades_b,grades_c,grades_d,grades_e,grades_f,"BOOL_OP,OR,COMPOSITE_TEST,""""""1"""""",TEST_CLAUSE,CASE_INSENSITIVE_TEST @Value(DataItem) CONTAINS alternative",@Value(DataItem) CONTAINS alternative,"BOOL_OP,OR,COMPOSITE_TEST,""""""1"""""",TEST_CLAUSE,CASE_INSENSITIVE_TEST @Value(DataItem) CONTAINS flexible",@Value(DataItem) CONTAINS flexible,"BOOL_OP,OR,COMPOSITE_TEST,""""""1"""""",TEST_CLAUSE,CASE_INSENSITIVE_TEST @Value(DataItem) CONTAINS urban",@Value(DataItem) CONTAINS urban,"BOOL_OP,OR,COMPOSITE_TEST,""""""1"""""",TEST_CLAUSE,CASE_INSENSITIVE_TEST @Value(DataItem) CONTAINS pct_peak_single",@Value(DataItem) CONTAINS pct_peak_single,"BOOL_OP,OR,COMPOSITE_TEST,""""""1"""""",TEST_CLAUSE,CASE_INSENSITIVE_TEST @Value(DataItem) CONTAINS pct_peak_combination",@Value(DataItem) CONTAINS pct_peak_combination,"BOOL_OP,OR,COMPOSITE_TEST,""""""1"""""",TEST_CLAUSE,CASE_INSENSITIVE_TEST @Value(DataItem) CONTAINS truck",truck CONTAINS truck,"BOOL_OP,OR,COMPOSITE_TEST,""""""1"""""",TEST_CLAUSE,CASE_INSENSITIVE_TEST @Value(DataItem) CONTAINS pct_dh_single_unit",@Value(DataItem) CONTAINS pct_dh_single_unit
    @Value(DataItem) CONTAINS curve -> SubstringExtractor
    @Value(DataItem) IN grades_a,grades_b,grades_c,grades_d,grades_e,grades_f -> SubstringExtractor_2
    @Value(DataItem) CONTAINS alternative -> StringReplacer_4
    @Value(DataItem) CONTAINS flexible -> StringReplacer_5
    @Value(DataItem) CONTAINS urban -> StringReplacer_6
    @Value(DataItem) CONTAINS pct_peak_single -> StringReplacer_7
    @Value(DataItem) CONTAINS pct_peak_combination -> StringReplacer_8
    truck CONTAINS truck -> StringReplacer_9
    @Value(DataItem) CONTAINS pct_dh_single_unit -> StringReplacer_10
    <UNFILTERED> -> DuplicateFilter
SubstringExtractor
    END = 5
    RESULT_ATTR = DataItem
    SRC_STRING = @Value(DataItem)
    START = 0
    -> DuplicateFilter
SubstringExtractor_2
    END = 5
    RESULT_ATTR = DataItem
    SRC_STRING = @Value(DataItem)
    START = 0
    -> DuplicateFilter
StringReplacer_4
    CASE = NO
    FIND_TEXT = alternative_route_name
    NO_MATCH = _FME_NO_OP_
    REGEXP = NO
    REPLACE_TEXT = route_name
    SRC_ATTRS = DataItem
    -> DuplicateFilter
StringReplacer_5
    CASE = NO
    FIND_TEXT = thickness_flexible
    NO_MATCH = _FME_NO_OP_
    REGEXP = NO
    REPLACE_TEXT = thickness_flex
    SRC_ATTRS = DataItem
    -> DuplicateFilter
StringReplacer_6
    CASE = NO
    FIND_TEXT = urban_code
    NO_MATCH = _FME_NO_OP_
    REGEXP = NO
    REPLACE_TEXT = urban_id
    SRC_ATTRS = DataItem
    -> DuplicateFilter
StringReplacer_7
    CASE = NO
    FIND_TEXT = pct_peak_single
    NO_MATCH = _FME_NO_OP_
    REGEXP = NO
    REPLACE_TEXT = pct_dh_single
    SRC_ATTRS = DataItem
    -> DuplicateFilter
StringReplacer_8
    CASE = NO
    FIND_TEXT = pct_peak_combination
    NO_MATCH = _FME_NO_OP_
    REGEXP = NO
    REPLACE_TEXT = pct_dh_combination
    SRC_ATTRS = DataItem
    -> DuplicateFilter
StringReplacer_9
    CASE = NO
    FIND_TEXT = truck
    NO_MATCH = _FME_NO_OP_
    REGEXP = NO
    REPLACE_TEXT = nn
    SRC_ATTRS = DataItem
    -> DuplicateFilter
StringReplacer_10
    CASE = NO
    FIND_TEXT = pct_dh_single_unit
    NO_MATCH = _FME_NO_OP_
    REGEXP = NO
    REPLACE_TEXT = pct_dh_single
    SRC_ATTRS = DataItem
    -> DuplicateFilter
DuplicateFilter
    INPUT_ORDERED_CHOICE = No
    KEYATTR = DataItem
    UNIQUE -> ListBuilder
ListBuilder
    LIST_ATTRS_TO_INCLUDE = DataItem
    LIST_NAME = _list
    -> ListExploder
ListExploder
    ATTR_ACCUM_MODE = Merge List Attributes
    ATTR_CONFLICT_RES = Use List Attribute Values
    INDEX_ATTR = _element_index
    LIST_ATTR = _list{}
    ELEMENTS -> TestFilter_12
    <REJECTED> -> TestFilter_12
TestFilter_12
    DEFAULT_VALUE = <UNFILTERED>
    PASSED_TEST_GROUP_OUTPUT = FIRST
    TEST_LIST = "BOOL_OP,OR,COMPOSITE_TEST,""""""1"""""",TEST_CLAUSE,TEST DataItem ATTRIBUTE_VALUE_NULL """,DataItem ATTRIBUTE_VALUE_NULL
    <UNFILTERED> -> TestFilter_17
TestFilter_17
    DEFAULT_VALUE = <UNFILTERED>
    PASSED_TEST_GROUP_OUTPUT = FIRST
    TEST_LIST = "BOOL_OP,COMPOSITE,COMPOSITE_TEST,""""""1"""""",TEST_CLAUSE,TEST $(ChooseYearDeletion) = ALL",__DeleteChoice_ = ALL
    __DeleteChoice_ = ALL -> SQLExecutor_2 [INITIATOR]
    <UNFILTERED> -> SQLExecutor [INITIATOR]
SQLExecutor_2
    COMBINE_ATTRS = Result Attributes Only
    COMBINE_GEOM = Initiator Geometry Only
    DATASET = HPMS
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = HPMS
    MSSQL_ADO_QUERY_FEATURE_TYPES_FOR_MERGE_FILTERS = Yes
    OUTPUT_FEATURES_DISPLAY = Schema and Data Features
    SQL_STATEMENT = DELETE from @Value(DataItem) WHERE 1=1
SQLExecutor
    COMBINE_ATTRS = Result Attributes Only
    COMBINE_GEOM = Initiator Geometry Only
    DATASET = HPMS
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = HPMS
    MSSQL_ADO_QUERY_FEATURE_TYPES_FOR_MERGE_FILTERS = Yes
    OUTPUT_FEATURES_DISPLAY = Schema and Data Features
    SQL_STATEMENT = DELETE from @Value(DataItem) WHERE DataYear IN ($(ChooseYearDeletion))
